// SPDX-License-Identifier: Apache-2.0 AND LGPL-2.1-or-later
package YuanxuPayloadOwnership {
    requirement def NamedValueScopeAdmission {
        doc /* Module publication, scope and dependency declarations use named
               Types. Do not retain the predicate-contract wrapper or a
               legacy dispatch fallback in this boundary. Runtime validate owns
               value normalization/refusal; the existing Context policy runs on
               that exact checked subject. Explicit contextual SourceAdmission
               obligations remain their own domain protocol, not Scope Types.
               Lean owns ordered value/policy composition and subject retention;
               existing admission-body/replay-ownership Quint models own callback
               and independent-return authentication. Runtime tests must check
               metadata mutation, refusal order, both requirements, parent cache
               separation and cold payloads. Selection still preflights actual
               descriptors; no Type check or source certification is postponed. */
    }
    requirement def PrivateCatalogCollection {
        doc /* Upstream ae190d1 folds private vector/RBTree entries into the
               same full ordered carrier, then applies existing first-name
               policy and final pair capture. PayloadSharing.privateCatalogFoldOrder
               owns the list equation including duplicates. Runtime multi-root
               tests own vector/tree correspondence, uninterned key identity,
               false payloads, callback identity, detached public pairs and
               persistent revisions. Existing replay/retention Quint models own
               temporal authentication; no duplicate fold state machine. This
               removes intermediate snapshots, not read identities or edges. */
    }
    requirement def PublicPrecedenceSnapshotBoundary {
        doc /* Upstream 89febc8 returns a fresh public C3 list spine. Core's
               source precheck and origin walk discard that public result and
               inspect already existing runtime metadata. On a present runtime
               precedence cache, avoid calling the snapshot producer. On a cold
               or invalidated cache, keep the exact public preparation call,
               its hooks, refusal and canonical C3 validation. Do not expose or
               mutate the canonical spine. Lean reuses ConstructionCache's
               lookupOr_present/lookupOr_missing laws; runtime tests establish
               this Scheme cache-branch correspondence and invalidation. Existing
               RoleFunction/ReadRetention Quint own callback and receiver state
               transitions. This allocates no new temporal model or cache. */
    }
    requirement def SourceWindowAttribution {
        doc /* Use 20.24's actual phase/guard/source trace, not guard count times
               an assumed closure size. Existing byte windows may share within
               one pure interval; they must not span Type initialization,
               Contract callbacks or independent return authentication. Lean
               Admission.SourceWindows owns stable-world byte reuse and complete
               requirements; existing Quint SourceWindows owns effect boundaries
               and missing-evidence counterexamples. Runtime tests own callback
               and filesystem correspondence. No second model, source-result
               cache, manual purity flag or omitted observer is authorized. */
    }
    requirement def ReplayRouteRunAttribution {
        doc /* Measure CPU and wall time at the existing Reader replay sites.
               In one callback-free native pass, consecutive records can
               share a route only for the same live receiver and storage.
               Authenticate issuance, key and slot state in original order.
               A return pass after Gerbil, a callback or observer delivery
               starts a fresh route check. Lean PublicationReads models the
               same-route premise and refusal order. The Scheme receiver
               census establishes frequency, not native state stability.
               An identical Gerbil wrapper class can have a changed slot
               map. Resolve field offsets in the live map before reading
               the field. SourceClosureWork.same_class_does_not_pin_route_offset
               and the Scheme class-retarget control preserve this refusal. */
    }
    requirement def PreparedRoleSourceObligations {
        doc /* The Reader resolves role paths at their original checks after
               package and prelude admission. A prepared row is equivalent
               only while that path binding holds. An open source observer
               can retarget a later role during the same guard. Lean
               PublicationReads.retargeted_role_cannot_reuse_prepared_path
               and the candidate-stage control require the live refusal.
               Resolve each role at its original checkpoint and retrieve
               its optional captured text in one lookup. A present role
               still reads its current bytes and an absent role still checks
               for a newly created input. Lean PublicationReads
               role_text_lookup_preserves_live_check preserves either check. */
    }
    requirement def ClosedFrameCaptureOwnership {
        doc /* Distinguish the literal-slot lowering premise from the shared
               interpreter environment held by the core and features thunks.
               PublicationReads.frame_environment_survives_either_slot
               models reachability for both original edges. The terminal
               Scheme cuts compare both orders. Any release needs to remove
               the unnecessary shared capture while keeping the owner role
               resolver and original lazy computations. Direct private
               delivery binds the original resolver only in the core SlotSpec.
               PublicationReads.private_core_slot_preserves_owner_and_resolver
               owns the captured-argument refinement. */
    }
    requirement def CompactReadReceiptRepresentation {
        doc /* The receiver may represent its preparation receipt and first
               ordinary receipt directly. A second distinct ordinary key can
               promote the directory while preserving every issued record
               identity. LeanPoo PreparationEvidence.ReadDirectory proves
               lookup/update correspondence and equal live-check results.
               The Scheme candidate authenticates the actual compact or
               table route and the original receiver generation on each
               side of effects. Core's read projection must use the native
               receipt lookup before this producer is adopted. SourceWindows
               Quint remains the effect-boundary model. Retention diagnostics
               do not qualify a replacement. */
    }
    requirement def DirectoryPublicationCoverage {
        doc /* A sparse demand observes its reached paths. A global directory
               policy requires all facts that can change its ordered refusal.
               Admission.SourceWindows proves the indistinguishable-world
               counterexample, preservation of the first refusal for a
               covered cut, rejection across authority or revision, and
               composition with unaffected summaries for a controlled edit.
               Scheme must establish exact listing/kind coverage and live
               generation ownership before consuming such a cut. Existing
               SourceWindows Quint still requires fresh checks around effects.
               Uncontrolled filesystem input retains independent live checks. */
    }
    requirement def SupportedComponentRepair {
        doc /* An upstream POO revision may add or retire owners. Before
               masking inactive positions, certify the new rows and every
               surviving reader of retired providers. The repair region uses
               forward and reverse reachability over the union of old and
               new edges. LeanPoo SupportedComponents proves exact cold SCC
               membership and order after projection through the successor
               roster. Remapped members also require quotient edge checks
               for readers outside the repair region. GraphOperations Quint
               covers declared structural closure, and PersistentSelectedHead
               covers stale head/fence rejection. Neither runs the SCC walk.
               The POO source editor candidate appends private witness
               positions without recycling retired addresses. DependencyRows
               proves position uniqueness and roster correspondence. The
               existing reverse index supplies retired providers' surviving
               readers for ordered source admission. The Scheme candidate
               repairs the partition and condensation under the same staged
               publication and splices the group witnesses using predecessor
               and successor positions. Large workload and downstream
               qualification remain distinct gates. */
    }
    requirement def LoadingStageEvidence {
        doc /* Library compilation, selected-graph construction, demand of a
               selected business scope and runtime compiled-module loading are
               separate stages. The 16/32 retention census constructs and admits
               a selected graph: its types/interface expansion count is NOT a
               business-role load count or a ten-thousand-module load receipt.
               Runtime build preparation runs outside loading measurements.
               The eventual 10000-module loading gate retains 2 GiB and its
               existing timeout; bounded diagnosis does not discharge that gate.
               No known-failing scale rerun is authorized by a small improvement.
               SysML owns this allocation; no duplicate Lean/QNT timing model. */
    }
    requirement def DirectCaptureOwnership {
        doc /* Issuer closures keep original record/checker/receiver identities;
               bound-self functions keep receiver-local identity and preparation
               semantics. Equal code or printed payload grants no pooling right.
               Scheme counts closure BODY bytes separately from direct referent
               bodies, reports each referent's identity and edge multiplicity,
               and keeps receiver/context/table frontiers explicit. Per-family
               unions overlap and MUST NOT be added as exclusive heap bytes.
               Lean reuses sharedNodeAccountedOnce, distinctEnvironmentRetained
               and weightedSupportPartition; these do not prove opaque capture
               immutability. Existing ReadRetention QNT retains every edge and
               effect/return authentication, both requirements and parent/child
               isolation. New sharing requires a concrete producer write and
               invalidation boundary; no new cache or acceptance result. */
    }
    requirement def OriginPointLookup {
        doc /* Source attribution asks for one local specification at each
               visited receiver. Use the runtime persistent catalog's first-name
               index rather than allocating every public entry pair for assq.
               Keep actual SlotSpec and descriptor identities, original C3 and
               row order, inherited source requirements, opaque barriers and
               getter/currentness boundaries. False metadata is PRESENT: only
               the private missing sentinel is absence. No descriptor getter
               or role is materialized by this query. Lean owns ordered first
               lookup and presence refinement through existing LeanPoo Storage;
               ReadRetention QNT continues to own temporal controls. Scheme
               owns the runtime map/index correspondence and false-barrier,
               cc/right-hand-origin, source-change and real Scenario tests.
               This removes temporary reflection snapshots, not original issued
               records, retained source text or whole-VM roots. No memory scale
               closure or performance improvement follows without measurement. */
    }
    requirement def ImportedEntryLifetime {
        doc /* Directory Fixture release does not unload an imported Gerbil
               entry's global exports. The census uses weak values to witness
               the previous namespace and Graph after Case unwind; an existing
               runtime-cell-only path module-0/tests/source/selected-graph still
               reaches that exact Graph. Do not call this private duplication,
               exclusive per-module memory, or permission to clear globals.
               Runtime owns this liveness correspondence; existing Lean support
               accounting does not prove GC dominators. QNT keeps its separate
               currentness/effect obligations rather than duplicating a heap
               model. The actual 10000-module worker has a fresh runtime entry;
               this census finding does not excuse its capacity failure. */
    }
    requirement def ObservedNamesSnapshot {
        doc /* Runtime structural records own a name-list spine; public reflection
               owns another. Core dependency projection compares finite symbol
               sequences for this ONE structural field, not pointer identity.
               Keep the original observed token, receiver revision, instance and
               ordinary cached-value identities. Final runtime authentication and
               all effect/return guards remain independent. No getter or checker
               callback executes in this metadata projection. Missing observation,
               changed receivers, cold leaves and malformed snapshots fall back.
               Lean owns list-copy/ordered projection equivalence; existing QNT
               ReadRetention/SourceWindows own missing evidence and mutation.
               Runtime tests establish the distinct spines and forbid forcing a
               replaced cold module-id. This is a producer API migration, not a
               new cached admission or an application-issued read record. */
    }
    requirement def SelectedMethodDemandLayout {
        doc /* The two maintained role-analysis access sites request runtime
               demand-filled slot caches. Keep actual MOP eligibility and
               default declaration replay unchanged; open carriers use Generic.
               Runtime preparation still validates the full specification and
               invokes hooks in order. Only unrelated VALUE prefill is avoided.
               The selected body is captured before the ownership callback,
               and runtime revision/receiver/layout guards authenticate each read.
               LeanPoo Representation owns shape/cell guard separation; existing
               QNT RoleFunction owns live eligibility and independent checks.
               Runtime demand-layout controls and real Scenario tests must qualify
               the correspondence; reduced read counts alone prove nothing. */
    }
    requirement def PersistentDeclarationCatalog {
        doc /* Runtime prototype maps own declaration membership and order.
               Core must use prototype-map-length for cold membership policy;
               pair?/null? are not predicates on the new storage. Attribution
               reads the public owned object-declarations snapshot. No descriptor
               getter runs merely to distinguish an empty catalog. Lean reuses
               LeanPoo Representation.entries_packWith/first and Core's
               catalogInspectionPreserved; Scheme checks empty/nonempty compact
               and tree maps and unforced descriptors. Existing QNT RoleFunction
               owns fallback for open metadata, currentness and observers; it
               does not duplicate the immutable storage proof. Runtime sharing
               never permits sharing receiver cells or issued-read identities.
               The new revision is not releasable until the prior issuer,
               construction and observer guards qualify in the same cohort. */
    }
    requirement def RuntimeSpecificationSuffix {
        doc /* Latest POO validates contributions before binding only the
               surviving chain after a constant, thunk or self specification.
               Core does not infer super-independence from function source,
               cached values or a purity tag. Lean reuses SlotSpec/Method with
               independentSpecificationDropsPrior; computed methods stay open.
               Extensional equality does not prove Scheme procedure identity or
               mutable specification capture time. Runtime refusal and hook-order
               tests and Scenario currentness provide that correspondence.
               Existing QNT RoleFunction/ReadRetention own callback boundaries;
               no duplicate temporal or representation model is introduced. */
    }
    requirement def CompilerSupportAttribution {
        doc /* Scheme follows already allocated context-to-context fields and
               counts their runtime table identities once; it never forces a
               phase frame, module initializer or slot for measurement. Closure
               code parents are runtime procedure identities, not one new code
               allocation per closure. VM live bytes remain whole-process data.
               Lean PayloadSharing sharedNodeAccountedOnce and
               weightedSupportPartition own finite support accounting, not GC
               dominator ownership or opaque procedure sizes. QNT SourceWindows
               retains effect/currentness/order boundaries; no second accounting
               model is added. A near-constant 16/32 delta is a hypothesis of
               shared support, never permission to remove dependencies or cache
               admission. Production changes require concrete binding/phase and
               ordered callback correspondence plus the real Scenario controls. */
    }
    requirement def FactoryLanguageFrame {
        doc /* Internal public-binding factories use Gerbil's existing runtime
               prelude context as the language parent, rather than importing
               every language alias into each new top table. Each invocation
               still creates its own top context, imports/resolves the public
               target anew and restores dynamic context on success or failure.
               No runtime function, source approval or admission result is cached.
               Lean Building.Inputs owns lookup equivalence under actual binding
               identity/phase correspondence. Runtime bootstrap controls check
               all language exports and missing-target restoration. Existing QNT
               SourceWindows owns independent effect/freshness boundaries; there
               is no second QNT model of lexical lookup. Strong-name collisions
               require a runtime compatibility control, not an identity assumption.
               Build entry remains only a std-make-spec consumer. */
    }
    requirement def AdjacentIssuedAuthentication {
        doc /* In runtime require-current!, authenticate the issued record once,
               then use the existing private metadata-route and issued-current
               checks. The public object-read-current? still authenticates its
               own callers. Keep preflight, each visit and final authentication;
               never transport authentication across an observer or effect.
               Runtime route checks use actual class/backend/procedure identities,
               not caller purity labels. Lean IssuedRead owns adjacent-result and
               first-error equivalence; existing QNT IssuedRead/SourceWindows
               own callback mutation and independent return refusal.
               Runtime tests establish source correspondence. Raw FFI/global
               kernel replacement is not certified by the serial model. */
    }
    requirement def LiveDependencyCursor {
        doc /* Keep the active siblings and postorder callback in tail arguments;
               allocate a suspended frame only on entering a new runtime context.
               Keep identity marking before descent, alias normalization, cycle
               refusal/termination, pruning and callback order. Do not mutate
               runtime metadata or share frames across calls/continuations.
               Lean Admission.DFSFrames cursor_enter/return_refines reuse the
               existing frontier model; runtime tests own postorder callbacks,
               pruning and exception identity. QNT IdentityDFS owns temporal
               source/receiver/final-check counterexamples, not a second cursor
               model. Allocation counts are not retained byte measurements. */
    }
    requirement def CompilerValueCapture {
        doc /* Build Entry identity/path/options/input/owner/contributor and a
               prepared input's path/identity/guard are immutable lexical values.
               Use runtime lexical slot captures, not computed getter wrappers.
               Keep compiler forms, receiver formulas, defaults and effectful
               methods demand-computed. Do not merge receiver or read identities.
               Lean Building.Inputs owns lexical_value_identity and receiver
               independence; runtime reflection and real admission tests establish
               the concrete correspondence. Existing SourceWindows/CoreBuildHandoff
               QNT retain temporal refusal ownership; add no duplicate model. */
    }
    requirement def ClosedInterpreterPublicationDelivery {
        doc /* Only a private interpreter wrapper whose Gerbil expansion proves
               the stock declaration grammar may deliver its original POO
               value directly to its Reader. Bind delivery to the exact native
               Context, accept it once and leave the native promise with void.
               Keep the lexical role resolver and all owner guards. Compiled
               and open declarations retain the native export and lookup.
               Named Feature lists retain declaration expansion to capture
               the reader bound to that owner before any Feature is demanded.
               Checks before expansion, after evaluation and during admission
               keep their original order and refusal. Lean PublicationReads
               proves delivery identity and refusal order. Runtime verification
               owns the closure grammar and Gerbil result correspondence.
               A shared assembly may describe only reads in an individual
               demanded computation. Resolve role receiver, role alias and
               dependency separately, in original order, against the invoking
               owner and captured resolver. Keep separate checks on the live
               state after Gerbil expansion and after the author callback. */
    }
    requirement def StockAuthoringProfileCheckpoint {
        doc /* Read the maintained Profile on every owner invocation. Its
               native slot may retain a closure over the private one-root
               replay spine for the signed record. Select it only when the
               newly observed record is identical and the caller has no
               open slot observer. POO freshly authenticates its full
               traversal and return. Open or changed receivers preserve
               original reads and fallback. Lean PublicationReads models
               the exact issued root order and refusal. Omitting this root
               requires coverage of its native support at that same boundary.
               Authenticating the other preparation reads does not establish
               this coverage. Lean profile_omission_can_hide_native_refusal
               preserves this independent failure. Preserve the original
               return refusal order when separating traversal support.
               Lean nested_lane_return_can_change_first_refusal shows why
               nesting protected replay calls does not establish this order.
               An observer may retain and mutate a validation receipt.
               Receipt kind does not establish privacy. Lean
               projected_private_read_window requires the exact retained
               preorder and live evidence for omitted records separately on
               both sides of an effect. Resolve the actual evidence Type's
               element method once. Before passing a receipt to a replaced
               method, run the existing open-boundary check. Lean
               replacement_evidence_method_cannot_outrun_refusal keeps this
               check ahead of method execution.
               Native Record slot checking may demand the nested classifier
               without the Yuanxu predicate wrapper. Check the exact
               delivered method before it receives the classification receipt.
               Preserve earlier field and method-resolution refusals. Lean
               replaced_nested_evidence_cannot_outrun_refusal covers this order.
               The actual Slot field checker also receives the entire Record.
               Guard a replacement on its delivered method even when dispatch
               selects a different Slot descriptor Type.
               Guard the Interface's selected outer Profile validator as well.
               It may allocate receipts before calling any Record predicate.
               Guard the delivered producer methods of the stock Profile,
               executor Contract and source role Contract at their existing
               call boundary. A replaced source role admission can mint and
               retain evidence before Record validation. A refusal at entry
               precedes the first such callback.
               The role value Contract's field and prepared normalization
               methods can retain the derived checked receiver. Authenticate
               the open boundary before delivering a replaced method.
               A success-only Profile value lane requires custody of the
               producer, preserved normalized child identities and independent
               support for root and child evidence acceptance. Decline the
               lane before running an open callback. Use the complete native
               refusal path when any premise fails.
               An owned derived record can become stale through an external
               ancestor without escaping. An omitted record that can fail
               needs an earlier retained check that refuses first. Establish
               this coverage separately at entry and return. Preserve the
               original signed order of all retained records.
               Retained replay roots must also be closed over their signed
               dependency edges. Dropping a root cannot suppress a read
               that another retained record still demands.
               Producer custody must survive publication. A later reader of
               the Graph can obtain the original issued Profile descendants,
               including constructor receipts, through native observation.
               Removing such a receipt from its route must still refuse.
               A read-only warm entry may combine birth and live checks
               under the same input state. A failed combination must restore
               the original refusal precedence. Preserve the independent
               return sweep and use the original path around effects.
               Attribute replay visits per checkpoint and retained records
               by identity across owners. Repeated traversal of a shared
               Profile receipt increases replay work without creating a new
               receipt receiver for each owner. */
    }
    requirement def PublicationRootSegments {
        doc /* A linked publication owns the original preparation and
               admission read spines. A native checkpoint that needs one
               spine joins them for that invocation. The Graph forwards
               the two segments to its existing POO index in original
               owner and phase order. Observed checks keep their separate
               boundaries. Lean PublicationReads.flatten_root_segments
               preserves the ordered signed input and the first refusal.
               PublicationReads.join_on_demand_preserves_guard_input
               preserves capture-time eligibility even when the observer
               is absent at a later invocation.
               Dependency projection resolves its first three membership
               probes in the original capture. A wider projection builds
               the same temporary eq? index over those roots. Lean
               bounded_recorded_lookup_preserves_ordered_membership keeps
               the query order and answers. No live check is removed. */
    }
    requirement def RecordedReaderHandoff {
        doc /* A protected native frame authenticates entry before the
               prepared input action and authenticates return before
               accepting its result. Authentication does not emit business
               reads. The action delivers each original read to the caller.
               A refused entry emits nothing. Action or return refusal
               preserves already delivered reads. Lean PublicationReads
               recorded_handoff_keeps_reads_when_return_refuses states
               this order. The native diagnostic does not establish
               unchanged live verdicts across the handoff. Independent
               Gerbil expansion and author effect checks remain required. */
    }
    requirement def CompletedWrapperRetentionEvidence {
        doc /* Measure the signed read frontier separately from native
               Gerbil registry aliases. Classify a temporary authoring
               Interface by its real producer and check incoming signed
               edges before considering a retention projection. A registry
               retirement requires private ownership, absence of future
               demand, and an exact Context comparison that preserves a
               replacement. Closed Interface delivery retires the expander
               aliases. The runtime import table can still own the same
               Context as a strong key after successful initialization.
               Observe that table under Gerbil's import mutex and distinguish
               Context retention from the void result of private delivery.
               The 64-owner census and 256-owner heap probe bound these
               candidates independently of the full capacity gate.
               Inspect each live native Context once by identity and
               distinguish registry aliases, bindings, expanded code and
               pending initializer thunks. Read settled promise state
               without forcing it. Direct fields do not measure all
               reachable heap or compiled code. The source guard spine
               and its scalar count advance together when a guard is
               enrolled. Observer delivery reads that count without
               traversing the accumulated spine. */
    }
    requirement def RoleInitializerTransferCustody {
        doc /* Role transfer consumes initializer support only with the
               private source and owner association for the same Context.
               The exact Interface wrapper completes its own source checks
               and forwards its original issued reads. Its initialization
               guard has no transfer row. Actual role guards remain attached
               to their native Contexts and authenticate again at transfer.
               Lean SourceClosureWork proves both cases. */
    }
    requirement def PreludeDependencyRepresentation {
        doc /* Keep Gerbil Core as a complete runtime import-set; filter the two
               POO constructor exports at the export boundary. Verify every public
               name/phase/resolved binding/weakness against the runtime baseline.
               Gerbil Core reexports must remain weak and direct POO constructors
               must win. All aliases remain in the runtime import-set. Lean owns
               same-owner reachability, not Gerbil's implementation or filesystem
               stability. Source guards before callbacks and before return remain
               independent. No modified expander context, replacement only-in macro,
               runtime Make fork or timestamp/admission cache is permitted.
               Apply this also to module-prelude and config-prelude. Audit
               terminal runtime bindings, not raw import-binding wrappers.
               Preserve the old export multiset by name/phase/weakness/binding;
               any language completion is explicitly limited to runtime Core
               public names and the original effective POO-shadowed lookup,
               weak so local definitions still win. Config adds ONLY the audited
               positive phases; runtime additions are refused by the test gate.
               Retain the specialized .def.
               Runtime controls compare actual DFS identity AND callback order
               against the former source forms in one process. Lean reuses
               grouped_runtime_owner_reachability and strong-lookup results;
               existing QNT owns effect boundaries, not a duplicate export model.
               CLI/source-entry and compiled-library probes are separate cohorts;
               never infer a production regression by mixing their counters. */
    }
    requirement def PrivateWrapperImportCustody {
        doc /* Compare a fixed wrapper binding by resolved identifier and
               expansion phase, with local and explicit imports taking
               precedence over the weak prelude. Verify the owner's direct
               imports and observable checks independently of binding
               resolution. A shared-prelude experiment
               removed three direct imports without a consistent CPU win.
               Retain the installed reader's native imports and its effect
               boundaries. A shared binding projection must preserve the
               ordered demand trace and the first native import refusal,
               including when the same demand also lacks a binding.
               The opt-in thousand-owner diagnostic attributes
               CPU and wall time with no source observer. Ordinary capacity
               uses its original measurement and watchdog. */
    }
    requirement def ExplicitImportProjection {
        doc /* A fixed-prelude Core library owner may retain a runtime:
               POO dependency and resolve ordinary POO bindings from the package
               prelude, avoiding a duplicate strong alias table. Independently
               reusable Scenario roles retain explicit bounded imports.
               Keep the runtime source and phase dependency edge and the exact
               export identity of each retained alias. Check ALL remaining strong
               bindings: a full gerbil/core import can shadow the weak POO
               make-object/object? bindings. Preserve deliberate shadows only.
               Do not narrow preludes,
               import reexports, syntax phases or custom contributor imports by
               a filename or a token-count heuristic. Runtime export inventory
               assists review; full compilation and consumer tests establish
               macro-use coverage. Lean Building.Inputs owns narrowed_import_edge
               and narrowed_binding_identity; remaining_bindings_preserve_identity
               requires complete remaining lookup, and runtime_import_edge keeps
               source/phase. Existing CoreBuildHandoff and
               SourceWindows QNT own independent currentness/effect boundaries,
               not a second lexical-binding model. No loader behavior, source
               admission, public value or process registry is replaced. */
    }
    requirement def CompilerMetadataSourceWindow {
        doc /* The Reader retains the actual private procedure delivered by
               its native preparation constructor. The existing preparations
               eq? input index links Context to input and input to constructor;
               Link binds an exact derived origin before the latest-view slot
               can change. Compiler index rows carry their actual input and a
               private constructor-derived validator; no object-supplied flag
               can substitute another selected closure. Both original bodies
               execute in order; SourceGuards.selectedNative and
               distinct_selected_keeps_both_bodies own this correspondence.
               Qualification compares actual receiver/prototype revisions,
               protocols, warm guard identity, selected compiler binding and
               the official expander package-cache object. Cold package lookup,
               protected metadata cache-miss, open Context and source/slot
               observers retain independent checks. No caller purity bit exists.
               Lean BoundaryComposition.SourceGuards owns extraction, refusal
               and ordered diagnostic laws; ReadOnlyEntry owns replay lowering.
               Existing SourceWindows/ReadOnlyEntry QNT own callback, source,
               parent-receiver, first-diagnostic and final-check transitions.
               Do not duplicate Lean's static origin equation in Quint.
               Only qualified compiler metadata segments reuse the existing byte window.
               A publication fence executes at its original position with fresh
               observations. Its source-only suffix is requalified separately;
               the final input remains fresh. Every original entry/guard and
               authentication occurrence remains ordered. Lean executeBlocks
               reuses ReadOnlyEntry execution for first-diagnostic preservation;
               SourceWindows QNT still owns effect/final-check failures.
               Every guard occurrence and native issued record remains. Recheck the
               captured entry revisions after foreign segments. Never memoize
               Link authentication in the byte table. Match the original Graph
               receiver and its captured revisions before enabling a prefix;
               inherited methods do not transfer their parent's authority. Keep
               the last publication outside it. Imports, native Make actions,
               writes and opaque printers remain effect boundaries; they clear
               enclosing byte observations on entry and exceptional resumption.
               Runtime tests establish the Scheme extraction correspondence;
               models alone do not establish installed runtime ABI or filesystem
               atomicity. External writers require independent final checks. */
    }
    requirement def WarmCompilerImportWindow {
        doc /* Share bytes only inside one existing compiler import request:
               actual core-import-module identity, a native cached context with
               the expected module identity, and the original compiler Entry
               held by the compiler index. Do not warm input.path to qualify.
               A publication requires existing Reader/Link qualification. A
               source input requires its exact live state from Graph's existing
               constructor-owned by-id index: prepare-build-source with native
               void context, matching checker, revisions, read route and package
               state. A source kind or supplied purity flag is insufficient.
               Reader-derived inputs without that association stay independent.
               Check live observer compatibility BEFORE without-observation;
               classification must not hide a foreign observer. Inherited
               Graph methods cannot transfer the parent's compiler-input owner.
               Both original guards and every MOP authentication still execute.
               Close the enclosing byte window before the request. Cold, foreign,
               unbound retained-source and observed paths remain independent; Make and
               module evaluation stay outside the shared request.
               Lean BoundaryComposition ImportFrame owns warm/foreign/cold
               lowering, lookupOr cache correspondence, guard diagnostic order
               and native registry insertion stability under fixed source identity.
               void_context_uses_source_requests and owned_input_keeps_both_guards
               specialize the existing extraction/window laws; they do not
               invent a second runtime cache or omit an authentication.
               Existing SourceWindows/ReadOnlyEntry QNT own callback mutation,
               receiver isolation, observation order and final checks. No second
               temporal model or runtime registry is introduced.
               Native registry writers and the installed importer are premises:
               arbitrary private-registry deletion, concurrent mutation and file
               atomicity are not established by a warm endpoint comparison.
               Runtime controls compare physical reads AND replay calls/visits;
               production measurements include qualification cost. */
    }
    requirement def BuildExecutionAccounting {
        doc /* Guarded byte-read totals do not include Gerbil's native parser
               and import I/O. Separate native context census, bound owner-path
               reuse, fresh source resolution, guarded reads and compiler jobs.
               A same-identity context census is diagnostic only: generated
               names may differ for copies of the same source. It neither
               authorizes reuse nor proves that no source is duplicated.
               Build execution is a separate workload from namespace acquisition.
               Attribute build.ss expansion/initialization, runtime library-spec
               discovery, selected compiler projection, runtime std/make, product
               repair/require and independent before/after source checks.
               Nested phase times are inclusive and must not be added twice.
               Ordinary gerbil build does not mint publication approval; explicit
               projection .compile retains issuance. Zero compilation does not
               mean zero dependency discovery, source validation or allocation.
               Existing SourceWindows Lean owns exact requirements under a
               stable pure read window. SourceWindows/CoreBuildHandoff QNT own
               effect separation and return checks. Neither proves that runtime
               import or Make coordination is pure. Keep those call boundaries;
               no byte window or acceptance result crosses them. Measurement
               scopes are not source observers and never change the read graph. */
    }
    requirement def BindingFactoryVersusRuntimeEntry {
        doc /* Platform data factories acquire one public binding through the
               official Gerbil import/eval-syntax machinery on every invocation.
               This works for source and compiled metadata and preserves runtime
               defining-context initialization/errors and successful reloads.
               It does not assert whole facade runtime initialization: that
               stronger boundary belongs to module-entry-action/module-action
               for actual runtime effects. Built-in declarative factories are
               not untrusted Module publication admission. No saved procedure,
               import registry, acceptance cache or user strategy flag is added.
               Existing ModuleDemand/ReadRetention QNT owns demand/currentness
               events; Lean's representation laws do not prove the two distinct
               runtime initialization contracts. Source/bootstrap, compiled
               factory and runtime-entry tests own that correspondence. */
    }
    requirement def NamespaceBuildProducerDemand {
        doc /* Namespace and selected-Graph demand do not require runtime
               initialization of the build producer, digest or packaging path.
               source/link delegates its existing lazy build-graph slot through
               module-binding-action; runtime binding initialization stays
               authoritative. No constructor identities or read records merge.
               Existing bootstrap roots retain source/build via build-projection,
               so compiler traversal still includes its metadata. Catalog
               presence is not currentness evidence: actual source observations
               remain demand-bound, not blanket admission. Build entry still
               admits the selected receiver after
               module initialization and keeps all original producer checks.
               Lean DemandMaterialization owns unrelated-demand preservation and
               receiver isolation, not dyld. ModuleDemand/ReadRetention QNT own
               demand, effects, both obligations and freshness. Scheme tests own
               actual unloaded/loaded state, errors, source bootstrap and plans.
               Whole-library initializer order is intentionally demand-driven;
               required build hooks/obligations are neither skipped nor memoized. */
    }
    requirement def RuntimeEntryAndIndexReuse {
        doc /* Stable Core/requires and prepared spec/admit-current access use
               runtime demand-filled slot sites. The latter invokes the current
               source checker on every request; no success verdict is retained.
               shared shapes certify offsets; receiver/revision/layout certify
               current cells. Lean DemandMaterialization owns represents,
               different_scope_rejected and reset_has_no_parent_cell, not
               effectful loading. Existing ModuleDemand QNT owns demand before
               business materialization and independent freshness/requirements;
               ReadRetention owns callback and source boundaries. Scheme tests
               establish actual .ref/inline and module-action correspondence.
               Runtime actions resolve the canonical binding each invocation
               through official load-module; no retained procedure/approval.
               Syntax exports stay with the expander, never runtime actions. */
    }
    requirement def SourceBootstrapEntry {
        doc /* A runtime loadable target is not implied by a source module's
               visible binding. An entry created while its actual owning runtime
               module context is evaluated from .ss uses official expander import;
               a compiled or unrelated caller uses module-action/load-module.
               Source initialization failure precedes canonical binding lookup.
               There is no module-not-found catch/fallback, saved business
               procedure, user phase flag or alternate initialized-module table.
               Existing ModuleDemand QNT owns demand-before-materialization and
               current admission; Scheme's empty-output build and compiled entry
               controls establish this interpreter/compiler correspondence.
               Lean's receiver-layout laws do not prove loader initialization. */
    }
    requirement def VerificationAllocation {
        doc /* Lean PayloadSharing owns binding injection, exact records and
               ordered edges, identity-union accounting and receiver/capture
               preservation. No duplicate PayloadSharing QNT model is kept.
               Existing QNT IssuedRootForwarding/ReadRetention/IncrementalRoles
               own callback-to-admission, invalidation and parent/child event
               traces. Scheme tests own actual MOP correspondence; the bounded
               census owns measured reachability and GC-live observations.
               ThunkConstruction QNT owns the distinct construction-event,
               next-function identity and metadata publication question.
               PayloadSharing Lean owns observation-relative identity
               projection laws; Scheme owns the runtime observation cut.
               POOF correspondence is specified in 20.13. Lean reuses Compose,
               TableRepresentation, CompiledPlan and ContextSlot for semantic
               refinement; SharedCellRefinement is not duplicated in QNT.
               ThunkConstruction owns only additional effectful exposure and
               callback schedules, not pointer-allocation or lookup proofs.
               DemandMaterialization Lean (20.14) owns partial/full open-method
               refinement and installed-handle preservation, using the locked
               CompiledPlan.resolve_sound. Scheme eq? correspondence remains
               runtime evidence; QNT does not duplicate these lookup laws.
               A new model requires a new question, not a second encoding. */
    }
    part def CanonicalContext {
        doc /* Installed Gerbil expander context and source index. Actual source
               authentication remains fresh at each admitted use. */
    }
    part def RoleContext {
        ref part imports : CanonicalContext;
        doc /* Local private constructor alias only. Original source lexical
               bindings and the runtime import dependency stay authoritative. */
    }
    part def Call {
        doc /* Distinct effective/invocation receivers. Within this call the
               existing argument list may be shared; callbacks stay distinct. */
    }
    part def IssuedRead {
        doc /* Original runtime identity, receiver, birth and ordered edges.
               No synthetic token or successful approval substitutes for it.
               Its issuer-private parent snapshot may store a single non-vector
               identity directly; empty/many/vector-valued cases stay dense.
               Lean proves exact sequence restoration; existing ReadRetention
               QNT owns temporal controls. Runtime tests check public mutation,
               inspector-copy isolation and actual retained-vector counts. */
    }
    part def ReceiverInstance {
        doc /* Receiver identity, monotone revision and runtime instance identity
               guard currentness. Cached cells are receiver-local, not pooled. */
    }
    part def TableStorage {
        doc /* Count container and entries by actual runtime flags. A strong
               table value is a strong edge; weak values are not roots. A
               weak-key table's value cannot be charged unconditionally: keep
               key liveness and collector semantics as explicit premises.
               Weak does not mean zero container/capacity cost. The diagnostic
               does not traverse entries or invoke rehash/hash callbacks. */
    }
    requirement def RetentionEdgeClassification {
        doc /* Lean PayloadSharing.tableValueRetained owns the conditional
               edge projection and key-liveness monotonicity. Existing QNT
               ReadRetention owns source changes, receiver separation, both
               requirements and laziness, not GC reachability. Runtime tests
               own actual flags/count layout and identity-union measurements.
               No collector lifetime or exclusive-byte theorem is claimed. */
    }
    requirement def OwnedReceiptInventory {
        doc /* One runtime names query replaces repeated presence queries only
               for an actual current-region factory receiver: original owned
               revision, unopened scope, compatible live observers/prechecks,
               and no previously exposed names cache. The existing derived
               constructor checks parent protocols/declarations. Otherwise keep
               ordinary per-field queries. Never filter issued records or cache
               membership/acceptance. Lean owns inventory/presence equivalence
               under complete inventory; existing RoleFunction QNT owns scope
               fallback and per-datum validation. Scheme owns the guard mapping,
               mutated/exposed inventory fallback and original read delivery. */
    }
    requirement def SyntheticCoreDescriptor {
        doc /* The Feature constructor publishes one complete default value.
               Internal mandatory-Core adapters may clone its runtime persistent
               specifications with three value overrides; receiver instances
               stay distinct. Runtime issuer-owned constructor identity, live
               observer scope and original template-read authentication gate
               this path at each call. Open constructors/observers retain the
               ordinary Feature-spec path. Lean owns put/frame equivalence;
               existing RoleFunction QNT owns actual-state route selection,
               and ReadRetention owns both requirements and source boundaries.
               No admission result or new Core cache protocol is introduced. */
    }
    part def Shape {
        doc /* Existing producer-owned name/index structure may be shared.
               It carries neither cached values nor a currentness verdict. */
    }
    part def PersistentSpecifications {
        doc /* Runtime persistent ordered snapshot. .cc already shares it;
               .+ may pass it directly instead of reflecting and rebuilding.
               Supported updates return a new snapshot. Public reflection
               keeps owned pairs; raw reflective mutation is not certified. */
    }
    part def ConstructorValue {
        doc /* An already evaluated Scheme argument, not an arbitrary delayed
               expression. Existing family macros bind it lexically and use
               runtime constant shorthand; no additional execution strategy
               or user configuration field is introduced. */
    }
    requirement def ConstructionRefinement {
        doc /* Lean PayloadSharing.constructorValueMethod and
               constructorValueInComposition reuse LeanPoo SlotSpec semantics.
               snapshotReflectionRoundtrip reuses runtime Representation laws.
               Existing ReadRetention QNT owns callback/source invalidation,
               joint requirements and parent isolation; no new structural QNT
               copy. Runtime controls own argument-once, hygiene, hook order,
               stable per-receiver thunk identity and persistent edit isolation.
               Body-byte savings do not prove a VM heap or scale bound. */
    }
    requirement def BoundedSpecificationStorage {
        doc /* Use runtime prototype-map compact policy at object/init for the
               newly declared method/default lists. Existing snapshots retain
               their policy; lists above the runtime bound promote to its RBTree.
               No admission result, receiver cells or SlotSpec identity is pooled.
               Lean constructorStorageObservations reuses entries_packWith for
               BOTH ordered lists. Existing QNT handles invalidation/effects;
               runtime controls own hook order, duplicate contributions, lexical
               slots, parent isolation and reflection. Byte acceptance requires
               the original post-operation identity-union census. */
    }
    part def CallbackEnvironment {
        doc /* One call/receiver owns mutable captures. Equal printed values
               cannot authorize merging closures or their environments.
               Warm/cold table entries may reference the same function. Lean
               owns the identity partition, Scheme owns raw non-forcing key
               extraction; existing QNT owns value-demand/currentness traces.
               No model here proves compute-slot construction hooks may be
               reordered just because a value is absent from the cache. */
    }
    requirement def OwnerShellAccounting {
        doc /* Shell projections and indirect environments share one identity
               union. Ordered marginal counts are not exclusive bytes; VM GC
               live is not a root dominator account. Nested owners, weak tables
               and descriptors remain explicit frontiers. Lean owns identity
               accounting; existing QNT owns temporal invalidation. */
    }
    requirement def CandidateSourceCatalog {
        doc /* One private Reader interpreter baseline may back many candidate
               source projections. Identical byte-object writes are inert;
               equal-text replacements and new paths require a private copy
               before mutation. Matching insertion sequences do NOT establish
               diagnostic order: a runtime counterexample rejected this attempted
               implementation. No shared-catalog production path is enabled.
               Lean owns lookup equivalence and its first-error counterexample.
               Existing ReadRetention QNT owns
               fresh authentication, callback and parent/child boundaries;
               no new approval state or duplicate temporal model is introduced.
               Scheme controls own exact byte identity and table iteration.
               This reduces structural allocation, not an admission verdict. */
    }
    requirement def TypedFunctionalAnalysis {
        doc /* One extensible Generic returns diagnostic lists. Every datum's
               result passes the runtime List-of-Diagnostic Type before merging;
               only an actual public admission demand constructs a receipt.
               This is a directed protocol migration, not default-only erasure
               of arbitrary receipt callbacks. Lean owns ordered aggregation
               and first-refusal propagation. Existing RoleFunction QNT owns
               per-row routing/carrier checks and open-hook fallback; result
               Type validation remains after production. ReadRetention
               owns source boundaries and receiver isolation. Runtime regression
               owns late registration, malformed contributor results, aggregate
               validation and actual admission-receiver construction counts.
               The consumer receives the same resolved role used for dispatch,
               including when a contributed method rebinds the Profile.
               On the authenticated default state, two Function profiles retain
               real methods selected by the Generic at initialization. Actual
               native C4 order selects the least-distance role parent; other
               axes must match their fixed prototypes. This eliminates repeated
               default descriptor/ranking preparation, not fresh authentication
               or output Type checking. Queries owns this lookup refinement;
               RoleFunction still owns extension and observer fallback.
               No approval or mutable invocation frame is reused. */
    }
    part def Loading {
        part context : CanonicalContext;
        part role : RoleContext;
        part call : Call;
        part read : IssuedRead;
        part instance : ReceiverInstance;
        ref part shape : Shape;
        part callback : CallbackEnvironment;
        dependency anchor from read to instance;
        dependency cachedCallback from instance to callback;
        dependency structuralIndex from instance to shape;
        dependency originalImport from role to context;
        dependency originalObservation from call to read;
    }
}
// Diagnostic union cardinality refinement: PayloadSharing.partitionLength,
// unionCountWithoutCopy, intersectionCountSymmetric and smallerIntersectionCorrect
// own the finite identity enumeration calculation. No QNT timing copy is added.
