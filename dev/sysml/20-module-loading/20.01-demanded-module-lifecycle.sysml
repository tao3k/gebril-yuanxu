// SPDX-License-Identifier: Apache-2.0 AND LGPL-2.1-or-later
package YuanxuModuleLoading {
    private import ScalarValues::*;
    part def SourceCatalogue {
        attribute entryCount : Integer;
        doc /* Directory/package identity and inert SourceRefs. Discovery must
               not expand roles, run user macros or admit domain objects.
               A wide-branch membership index projects the same ordered
               directory snapshot. A hit still checks the live path type.
               Full currentness still observes the directory listing.
               A large selection source compares exact decoded text through
               EOF with a bounded buffer inside one observation window.
               A guard and ordinary reader can share the observed text in
               that window. Each guard compares its own expected text.
               Effects require a fresh physical observation. */
    }
    part def SelectedDeclarations {
        attribute selectedCount : Integer;
        attribute sourceRevision : String;
        doc /* Runtime interface metadata: identity, requirements, feature
               decisions, role locations and source association. Dependency
               closure is not a list of linked business scopes. */
    }
    requirement def IndexedOwnerEligibility {
        doc /* Apply denial before selection, and consult policy only on a
               selection miss. Indexed membership may replace the list search
               when both symbol sequences are the live payloads of the same
               observation window. A matching receiver revision alone does not
               establish that a separately mutable sequence is unchanged. */
    }
    requirement def ProfileClassificationRevision {
        doc /* Preserve candidate directory order. Reclassify changed inputs
               only when an authenticated change set covers every differing
               classification input. Decoder policy is part of that input.
               Unknown revisions require complete Profile currentness. A tag
               match does not approve the selected owner's source bytes. */
    }
    part def PublicationPreflight {
        ref part declaration : SelectedDeclarations;
        attribute descriptorsValid : Boolean;
        doc /* Real publication admission demands Type descriptors for
               scope and dependency contracts. Config, Objects, Func and the
               export body stay cold. This is not domain admission. */
    }
    part def DemandedScope {
        attribute receiverIdentity : String;
        attribute sourceRevision : String;
        attribute featureDecision : String;
        attribute demandedCount : Integer;
        doc /* POO slots own role construction on actual access. Reuse
               requires exact receiver/source/feature/phase context. A parent
               cached scope is not a child's normalized configuration. */
    }
    part def ManagedDependencyPolicy {
        ref part declaration : SelectedDeclarations;
        doc /* Proposed gate between complete metadata selection and business
               activation. Bind actual native import owners and lexical aliases
               to admitted SourceRefs, requirement Contracts and current phases.
               Alias installation must not initialize every provider scope.
               Downstream applications supply no loader factory or purity flag. */
    }
    part def RuntimeReadSupport {
        attribute originalRecordCount : Integer;
        attribute orderedEdgeCount : Integer;
        doc /* Once issued, every original dependency remains. No observer
               event, miss, second requirement or stale record is pruned. */
    }
    part def PrivateLeafProjectionCandidate {
        ref part support : RuntimeReadSupport;
        doc /* The original local check authenticates the complete capture.
               A later representation may omit a direct root only after the
               producer proves that it is dependency-free, cannot escape, and
               cannot supply a later refusal. Keep the other original
               identities and their first-refusal order. Runtime projection
               requires evidence of non-escape for the actual producer. */
    }
    part def DirectoryReaderEntry {
        ref part support : RuntimeReadSupport;
        doc /* The directory factory owns the location check. POO authenticates
               the actual preparation roots before and after that closed check.
               The trailing policy and source checks still run. Custom
               callbacks, observers and all later effect boundaries retain
               independent authentication. */
    }
    requirement def DeferredPreparationHandoff {
        doc /* Keep location, policy, source, and prepared input enrollment in
               their original refusal order. Sharing the intermediate replay
               requires identical live verdicts at the omitted checkpoints.
               The native protected action suspends recording, observers, and
               prechecks. It may not enclose a required prepared checker read.
               PublicationReads proves the independent refusal and delivery
               premises. Gerbil expansion and author calls retain their own
               checks. */
    }
    part def InterfaceDatumProjection {
        ref part declaration : SelectedDeclarations;
        doc /* The private stock Interface datum read supplies both the
               binding check and deferred-role classification. Keep owner
               and native compiler identity independent. Custom readtables
               and source observers preserve separate reads. Release the
               datums before retaining the prepared declaration. */
    }
    part def ReaderFormProjection {
        ref part declaration : SelectedDeclarations;
        doc /* Store one Reader form lane for the admitted owner. Preserve
               native compiler forms separately. Selecting the deferred
               lane does not demand eager role forms. */
    }
    part def SessionReadRootProjection {
        ref part support : RuntimeReadSupport;
        doc /* Record ordered publication rows in the existing native
               unique collection. Retain first-occurrence identities and
               the complete signed dependency traversal. Replay still
               authenticates live reads independently. */
    }
    part def CandidateReturn {
        ref part support : RuntimeReadSupport;
        doc /* A fixed directory and source check may run inside the
               native protection of preparation and admission roots.
               A refused preflight restores the original preparation,
               source, admission order. Open callbacks keep their own
               checkpoints. Every successful return rechecks live roots. */
    }
    part def StockAuthoringRun {
        ref part support : RuntimeReadSupport;
        doc /* Share authentication only within an established closed run
               with unchanged stock-method support. Keep the ordered read
               delivery of each rule invocation. An author callback owns
               independent entry and return guards. The next run reads
               the post-effect state. */
    }
    part def StockAuthoringReadDelivery {
        ref part support : RuntimeReadSupport;
        doc /* Capture the exact ordered native read delivery in a local
               scope. Preserve all native checks. Forward original records
               together only when the maintained observer has no effects
               on their receivers. Otherwise use original delivery. */
    }
    requirement def ClosedStockDatumTrace {
        doc /* Share method support within a stock run only when owner binding
               and effect-free execution are independently established. Keep
               the exact common read occurrences before each row's owner
               suffix. Publish the original trace only after native return
               authentication. An effectful role getter, diagnostic Type,
               source observer or precheck retains the original operation and
               its independent guards. The protected replay action suppresses
               observation; running a body there requires proof that it can
               neither demand an effect nor suppress a required precheck. */
    }
    requirement def FixedSourceDispatchTrace {
        doc /* The maintained native method producer may retain its original
               ordered deliveries and a distinct receiver projection.
               Every source datum resolves the actual owner arguments and
               authenticates all signed records at native entry and return.
               Read the live receiver eligibility and mutable policy payload
               within that check. Forward original records after success.
               Actual body and diagnostic Type work use the caller scope.
               An incompatible entry uses ordinary dispatch. Preserve the
               original native refusal after selection. */
    }
    part def SourceAuthoringDecision {
        ref part authoring : StockAuthoringRun;
        doc /* Validate every actual datum. Source consumes a decision and
               optional diagnostic. An empty maintained result may omit its
               temporary receipt after native constructor, Type, prototype
               and warm owner fields are authenticated. Retain their actual
               reads. Changed Type and observer paths validate the ordinary
               receipt. */
    }
    part def ReadOnlyPublicationCheckpoint {
        ref part support : RuntimeReadSupport;
        doc /* Use native POO authentication for a validation-only traversal.
               The issuer retains the complete issued preorder and checks
               every live record before returning the fixed result. Source,
               policy and observer callbacks retain their original entry
               and return checks and observer delivery. A diagnostic count
               describes the completed native preflight. */
    }
    part def DeferredRoleSlot {
        doc /* Native slot construction shares one implementation.
               The role captures its own owner resolver.
               Each alias reads the current POO receiver and role value.
               The Gerbil wrapper and effect guards remain owner-specific. */
    }
    part def DeferredRoleLexicalSupport {
        ref part slot : DeferredRoleSlot;
        doc /* Closed payload syntax may use a conservative inventory of its
               lexical identifiers to limit the wrapper's role aliases.
               Unknown expansion retains every visible alias. An existing
               nonempty alias group observes its receiver once even if the
               restricted inventory is empty. Source syntax,
               receiver, owner resolver, demand and native return checks
               remain attached to the individual publication. */
    }
    part def DeferredInterfaceFrame {
        ref part lexicalSupport : DeferredRoleLexicalSupport;
        doc /* Gerbil emits delayed field bodies in the owning Context.
               A closed frame can use the common native POO slot constructor.
               The binder, ordered dependency reads and lazy receiver survive
               that lowering. Unknown syntax, local shadowing and other
               object options retain normal declaration expansion.
               Source and issued-read guards still enclose expansion and
               author effects. The hygienic wrapper captures the current
               owner's reader resolver through its existing parameter. */
    }
    part def LoadingWork {
        attribute expandedIdentities : Integer;
        attribute processedEdgeOccurrences : Integer;
        attribute exhaustedFrames : Integer;
        attribute demandedReceivers : Integer;
        attribute affectedReceivers : Integer;
        attribute membershipProbes : Integer;
        attribute dependencyBucketReads : Integer;
        attribute changedRankLabels : Integer;
        attribute inspectedIncidentEdges : Integer;
        doc /* Derived observations of the production algorithm, not policy
               flags or a second cache. Lean SourceClosureWork.Frames owns the
               recursive-frame/worklist representation proof and frame bound.
               Its descent law preserves pending order while the active
               sibling cursor stays in a loop argument. Only a nonempty
               sibling continuation needs a frame when descending.
               IncrementalRoles owns affected-owner correspondence.
               IndexedWork instruments the existing HashSet worklist. A
               completed walk charges each root/edge occurrence one probe
               and each reached owner one bucket. Resuming the same captured
               graph charges only newly reached buckets. A continuation
               retains unfinished work when new roots arrive. Retained-owner
               membership uses LeanPoo KeyIndex, with exact key equality.
               GeneralizedGraph permits reuse of checked order/rank for edge
               restrictions. Added edges must satisfy the retained rank or
               obtain a new checked schedule. These structural witnesses do
               not discharge an independent source or signed-read check.
               DependencyOrderRepair uses the existing LeanPoo directed path
               relation and schedule witness. A bounded path search exactly
               preserves insertion-cycle detection. Changed-rank incident
               edges and every added edge certify the new order. Reverse
               incidence is mandatory; a consumer outside the rank interval
               can still require value/source invalidation. Sorted sparse
               proposals have executable controls but no universal proposal
               completeness or native capacity proof yet. These observables
               do not claim Scheme has installed the proposed repair path.
               Costs of actual index primitives, Type callbacks, per-boundary source
               authentication and unique strongly held payloads remain separate.
               A linear DFS alone does not prove linear publication work,
               the applicable heap bound, or a wall-time deadline. Quint checks effect
               and mutation traces, not another copy of frame arithmetic.
               Physical source reads are attributed by actual init-source owner
               and authentication phase, without retaining another read graph.
               Lean SourceWindows owns stable-window requirement equivalence;
               it does not certify open observer callbacks as read-only or make
               equal-sized snapshots equivalent. Runtime controls own callback
               error identity, nested enrollment and fresh return observations.
               Context selected-membership uses one per-validation symbol
               identity index only after native cache/precedence/protocol and
               observer-state checks. Unknown observers and cold/hooked state
               retain original per-element reads. Lean SelectionIndex owns
               lookup and first-missing equivalence, not hash worst-case time. */
    }
    part def RuntimeCapacityWork {
        attribute selectedModules : Integer;
        attribute sourceObserverInstalled : Boolean;
        attribute firstGraphSeconds : Real;
        attribute firstValueSeconds : Real;
        attribute hotValueSeconds : Real;
        attribute changedValueSeconds : Real;
        doc /* The observed qualification workload retains all original events
               and assertions. Normal-runtime capacity is a SEPARATE std/test
               Case, using the same native init, role wrappers and module tree.
               Both workloads run as assertion functions in the current native
               std/test Case. No capacity Case may invoke another .run, CLI
               test command, compiler/signing pass or nested Harness. Tests of
               the explicit execution API remain separate end-to-end controls.
               Atomic entry invokes the installed test tool directly, without
               init selection or Script/Process construction. Independent build
               owns support issuance; module APIs and Cases own domain checks.
               The benchmark must not explicitly force complete graph admission
               before a value. Plain directory scope resolution starts at the
               requested owner. Signed Feature decisions, custom Contexts
               and realized package bindings retain their existing graph route.
               A cold export slot does not prove no internal graph was built.
               Use owner-qualified counters to assert every reached scope and
               every declaration admitted by the plain demand.
               It asserts no source observer is installed; it must not silently
               clear a caller's observer. Measure Graph demand separately from
               scope activation, value-cache access, independent admission,
               source preparation, compilation and Harness startup.
               A claimed Case stop must refuse the next genuine progress
               report on its owner before the relay changes. A local catch
               cannot replace the original rejection or extend the work.
               Change a real module's Config receiver, retain/replay original
               issued reads, and demand the getter again through native
               with-slot-dependencies. Assert exact computation counts and an
               unrelated hot identity. This explicit module getter is not
               automatic Loader enrollment or a cached admission verdict.
               Lean IncrementalRoles owns registration/affected correspondence;
               SourceWindows owns byte-sharing/independent-check equivalence.
               Other observations cannot certify an omitted effect window.
               An edit may be visible only there and restored before return.
               The withdrawn scratch experiment required exclusive access,
               a physical file open, comparison of only the overwritten
               prefix, and decoding through EOF. The v0.1.0 snapshot path
               has separate runtime correspondence obligations.
               Quint owns stale source, omitted requirements, parent receiver
               and effect traces, not elapsed-time or GC arithmetic.
               Native runtime timings and retained-memory observations qualify
               capacity; a model theorem alone cannot establish the budget. */
    }
    part def Admission {
        ref part scope : DemandedScope;
        ref part support : RuntimeReadSupport;
        doc /* Domain obligations, source association and plan identity must
               hold for the final receiver. No successful decision is cached
               across callbacks/effects; return-currentness remains fresh. */
    }
    part def CallbackFrame {
        ref part support : RuntimeReadSupport;
        doc /* One known effect boundary during demanded scope linking:
               requirement admission, factory, or scope admission. Authenticate
               entry and successful exit with independent source reads. Preserve
               callback failure rather than replacing it with a later stale
               diagnostic. An observer's start/end delivery is also an effect
               boundary; it cannot carry approval into the callback body.
               End delivery during failure unwinding must retain both original
               causes if it fails too. Lean Boundary.finishObserved owns this
               outcome algebra; Scheme checks actual exception identity and
               dynamic-wind delivery counts, including false-valued exceptions.
               Quint retains its effect/support/cleanup trace responsibility.
               Lean ManagedBinding.execute owns the integrated ordered reference
               flow. This does not prove arbitrary effects inside one callback
               read-only or make external file snapshots atomic. */
    }
    part def Loading {
        part catalogue : SourceCatalogue;
        part declarations : SelectedDeclarations;
        part preflight : PublicationPreflight;
        part policy : ManagedDependencyPolicy;
        part scope : DemandedScope;
        part callback : CallbackFrame;
        part admission : Admission;
        dependency sourceSelection from catalogue to declarations;
        dependency descriptorAdmission from declarations to preflight;
        dependency dependencyAdmission from preflight to policy;
        dependency actualDemand from policy to scope;
        dependency explicitAdmission from scope to admission;
    }
    requirement def NoEarlyRoleConstruction {
        attribute declarationOnly : Boolean;
        attribute roleConstructions : Integer;
        require constraint { not declarationOnly or roleConstructions == 0 }
        doc /* Proposed fast path only. A source/MOP-owned closed projection
               must establish this; an author's Boolean cannot authorize it.
               Unknown code/hooks take the existing full guarded path. */
    }
    requirement def SeparateCapacityWorkloads {
        attribute catalogueCount : Integer;
        attribute selectedCount : Integer;
        attribute demandedCount : Integer;
        require constraint { demandedCount <= selectedCount }
        require constraint { selectedCount <= catalogueCount }
        doc /* Keep the existing 10000-selected declaration gate at 2 GiB.
               Separately measure large catalogue/small selection and full
               business-scope activation. Never substitute one for another. */
    }
    requirement def CompleteSelectionBeforeExposure {
        attribute viewExposed : Boolean;
        attribute declaredDependenciesAdmitted : Boolean;
        attribute sourceOwnersBound : Boolean;
        require constraint { not viewExposed or
            (declaredDependenciesAdmitted and sourceOwnersBound) }
        doc /* Runtime-projected facts, not user policy switches. Lazy business
               access cannot hide disabled, undeclared or cyclic requirements.
               For a plain directory scope, the admitted dependencies are
               those reached from the requested owner. Explicit complete
               Graph requests and selections with Feature decisions retain
               the full selection. */
    }
    requirement def NoPrematureBusinessActivation {
        attribute businessRoleInitialized : Boolean;
        attribute providerSelectedAndEnabled : Boolean;
        attribute phasePermitsBusinessActivation : Boolean;
        require constraint { not businessRoleInitialized or
            (providerSelectedAndEnabled and phasePermitsBusinessActivation) }
        doc /* Core bootstrap/type-descriptor initialization is classified
               separately. This does not establish purity of arbitrary macros,
               unsafe reflection or direct foreign calls. */
    }
    requirement def BeforePublication {
        attribute published : Boolean;
        attribute descriptorsValid : Boolean;
        attribute finalReceiverAdmitted : Boolean;
        attribute sourcesCurrent : Boolean;
        attribute requiredModulesEnabled : Boolean;
        require constraint { not published or
          (descriptorsValid and finalReceiverAdmitted and sourcesCurrent and requiredModulesEnabled) }
    }
}
